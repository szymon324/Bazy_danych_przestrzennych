FME workspace zadanie_dodatkowe.fmw
Startup Python:
      import rasterio

Parameters:
- File = C:\Users\szymo\T2018_KAR_BUILDINGS.zip   # "" Select a File
- Nazwa_pliku_mapBox = NowyPlik   # Enter Text Data

Creator
    GEOMTYPE = Geometry Object
    NUM = 1
    CREATED -> HTTPCaller
HTTPCaller
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.mapbox.com/uploads/v1/szymonagh/credentials?access_token=sk.eyJ1Ijoic3p5bW9uYWdoIiwiYSI6ImNsZDUydjJxMTAxYTEzdXFocm9hOThwbnQifQ.G9G6P6qH8u6_0jNKeKmKrw
    TRANSFER_TIMEOUT_LENGTH = 90
    UPLOAD_CONTENT_TYPE = Text (text/plain)
    UPLOAD_FILE = $(File)
    UPLOAD_TYPE = Upload From File
    USE_COOKIES = No
    VERIFY_SSL_CERTIFICATES = Yes
    -> AttributeCreator
AttributeCreator
    ATTR_TABLE = SET_TO send = curl -X POST -H "Content-Type: application/json" -H "Cache-Control: no-cache" -d "{ \"url\": \"http://tilestream-tilesets-production.s3.amazonaws.com/60/_pending/9ck2r4pf6p72rr91kduzv4dlc/szymonagh\", \"tileset\": \"szymonagh.traverse-bay\", \"name\": \"$(Nazwa_pliku_mapBox)\"}" https://api.mapbox.com/uploads/v1/szymonagh?access_token=sk.eyJ1Ijoic3p5bW9uYWdoIiwiYSI6ImNsZDUydjJxMTAxYTEzdXFocm9hOThwbnQifQ.G9G6P6qH8u6_0jNKeKmKrw
    -> SystemCaller
SystemCaller
    CMD = @Value(send)
    -> Inspector
Inspector
